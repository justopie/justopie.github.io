(defun AddPointToGroup (intPoint objGroup / objQB)
  (if (and (= (type intPoint) 'INT)
           (= (type objGroup) 'VLA-OBJECT)
           (= (vla-get-ObjectName objGroup) "AeccDbPG")
           (not (ContainsPoint objGroup intPoint))
      )
    (progn
      (setq objQB         (GetQueryBuilder objGroup)
        strIncludedNumbers (vlax-get-property objQB 'IncludeNumbers)
      )
      (if (> (strlen strIncludedNumbers) 0)
        (vlax-put-property objQB 'IncludeNumbers (strcat strIncludedNumbers "," (itoa intPoint)))
        (vlax-put-property objQB 'IncludeNumbers (itoa intPoint))
      )
    )
  )
)
